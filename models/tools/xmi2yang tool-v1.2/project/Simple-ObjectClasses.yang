module Simple-ObjectClasses {
    namespace 'urn:onf:Simple-ObjectClasses';
    prefix Simple-ObjectClasses;
    list TestObject {
        key 'uuid';
        config true;
        leaf uuid {
            type string;
        }
        leaf TestAttribute1 {
            type string;
        }
    }
}
